-- OK: Everything is fine
-- Test for cross-file parameterized type specialization includes
-- This test verifies that when one parameterized type (like ProtocolIE-SingleContainer)
-- references a specialization of another parameterized type (like ProtocolIE-Field),
-- the include generation uses the correct parent type filename and struct form typedef.
-- This prevents the F1AP-style issue where includes reference non-existent files.

-- iso.org.dod.internet.private.enterprise (1.3.6.1.4.1)
-- .spelio.software.asn1c.test (9363.1.5.1)
-- .169

ModuleCrossFileParamSpecialization
    { iso org(3) dod(6) internet(1) private(4) enterprise(1)
        spelio(9363) software(1) asn1c(5) test(1) 169 }
DEFINITIONS AUTOMATIC TAGS ::= BEGIN

    -- Simulates F1AP's ProtocolIE-ID
    ProtocolIE-ID ::= INTEGER (0..65535)

    -- Simulates F1AP's Criticality
    Criticality ::= ENUMERATED { reject, ignore, notify }

    -- Simulates F1AP's Presence
    Presence ::= ENUMERATED { optional, conditional, mandatory }

    -- Simulates F1AP's PROTOCOL-IES class
    PROTOCOL-IES ::= CLASS {
        &id             ProtocolIE-ID UNIQUE,
        &criticality    Criticality,
        &Value,
        &presence       Presence
    }
    WITH SYNTAX {
        ID              &id
        CRITICALITY     &criticality
        TYPE            &Value
        PRESENCE        &presence
    }

    -- Simulates F1AP's ProtocolIE-Field parameterized type
    -- This is where specializations are defined
    ProtocolIE-Field {PROTOCOL-IES : IEsSetParam} ::= SEQUENCE {
        id          PROTOCOL-IES.&id            ({IEsSetParam}),
        criticality PROTOCOL-IES.&criticality   ({IEsSetParam}{@id}),
        value       PROTOCOL-IES.&Value         ({IEsSetParam}{@id})
    }

    -- Simulates F1AP's ProtocolIE-SingleContainer
    -- This is a typedef to ProtocolIE-Field and its specializations
    -- should reference ProtocolIE-Field.h, not non-existent specialization files
    ProtocolIE-SingleContainer {PROTOCOL-IES : IEsSetParam} ::=
        ProtocolIE-Field {{IEsSetParam}}

    -- Simulates F1AP's ProtocolIE-Container
    ProtocolIE-Container {PROTOCOL-IES : IEsSetParam} ::=
        SEQUENCE (SIZE (0..65535)) OF
        ProtocolIE-Field {{IEsSetParam}}

    -- Sample IE set (simulates F1AP-PDU-ExtIEs)
    SampleIEs PROTOCOL-IES ::= {
        { ID 1 CRITICALITY reject TYPE INTEGER PRESENCE mandatory },
        ...
    }

    -- Another IE set (simulates another F1AP IE set)
    AnotherIEs PROTOCOL-IES ::= {
        { ID 2 CRITICALITY ignore TYPE BOOLEAN PRESENCE optional },
        ...
    }

    -- Usage of ProtocolIE-SingleContainer with different IE sets
    -- These should generate typedefs that use struct form for
    -- cross-file specializations
    SampleContainer ::= ProtocolIE-SingleContainer { {SampleIEs} }
    AnotherContainer ::= ProtocolIE-SingleContainer { {AnotherIEs} }

    -- Usage of ProtocolIE-Container
    SampleList ::= ProtocolIE-Container { {SampleIEs} }

    -- Top-level PDU that uses the containers
    TestPDU ::= SEQUENCE {
        sampleContainer     SampleContainer,
        anotherContainer    AnotherContainer OPTIONAL,
        sampleList          SampleList
    }

END
