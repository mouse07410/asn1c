-- OK: PrivateIE-Field should compile with -fno-include-deps
-- Tests that IOC field types (like PrivateIE-ID) are included in header files
-- even when -fno-include-deps is used, preventing "unknown type name" errors.
-- This test reproduces and validates the fix for the F1AP compilation issue.

-- iso.org.dod.internet.private.enterprise (1.3.6.1.4.1)
-- .spelio.software.asn1c.test (9363.1.5.1)
-- .170

ModulePrivateIEField
    { iso org(3) dod(6) internet(1) private(4) enterprise(1)
        spelio(9363) software(1) asn1c(5) test(1) 170 }
DEFINITIONS AUTOMATIC TAGS ::= BEGIN

    -- Similar to F1AP's PrivateIE-ID (simplified as INTEGER for test)
    PrivateIE-ID ::= INTEGER (0..65535)

    -- Similar to F1AP's Criticality
    Criticality ::= ENUMERATED { reject, ignore, notify }

    -- Similar to F1AP's Presence
    Presence ::= ENUMERATED { optional, conditional, mandatory }

    -- Similar to F1AP's PRIVATE-IE-ID class
    PRIVATE-IE-ID ::= CLASS {
        &id             PrivateIE-ID UNIQUE,
        &criticality    Criticality,
        &Value,
        &presence       Presence
    }
    WITH SYNTAX {
        ID              &id
        CRITICALITY     &criticality
        TYPE            &Value
        PRESENCE        &presence
    }

    -- Similar to F1AP's PrivateIE-Field parameterized type
    PrivateIE-Field {PRIVATE-IE-ID : IEsSetParam} ::= SEQUENCE {
        id          PRIVATE-IE-ID.&id            ({IEsSetParam}),
        criticality PRIVATE-IE-ID.&criticality   ({IEsSetParam}{@id}),
        value       PRIVATE-IE-ID.&Value         ({IEsSetParam}{@id})
    }

    -- Similar to F1AP's PrivateIE-Container
    PrivateIE-Container {PRIVATE-IE-ID : IEsSetParam} ::=
        SEQUENCE (SIZE (1..65535)) OF
        PrivateIE-Field {{IEsSetParam}}

    -- Sample IE set (simulates PrivateMessage-IEs from F1AP)
    PrivateMessage-IEs PRIVATE-IE-ID ::= {
        { ID 1 CRITICALITY reject TYPE INTEGER PRESENCE mandatory },
        ...
    }

    -- Usage
    PrivateMessage ::= SEQUENCE {
        privateIEs  PrivateIE-Container { {PrivateMessage-IEs} } OPTIONAL
    }

END
