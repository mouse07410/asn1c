-- OK: Test WITH SYNTAX with consecutive field references
-- Issue: Unable to parse X.681 IOC with WITH SYNTAX containing
-- consecutive field references without literal separators

-- iso.org.dod.internet.private.enterprise (1.3.6.1.4.1)
-- .spelio.software.asn1c.test (9363.1.5.1)
-- .172

ModuleConsecutiveFields
	{ iso org(3) dod(6) internet(1) private(4) enterprise(1)
		spelio(9363) software(1) asn1c(5) test(1) 172 }
	DEFINITIONS AUTOMATIC TAGS ::=
BEGIN

-- CLASS with consecutive fields in WITH SYNTAX
EXTENSION ::= CLASS {
    &id    OCTET STRING (SIZE (16)) UNIQUE,
    &Type
} WITH SYNTAX {&id &Type}

-- Information object set using the above syntax
ExtensionSet EXTENSION ::= {
    { '0102030405060708090A0B0C0D0E0F10'H MyTypeA } |
    { '1112131415161718191A1B1C1D1E1F20'H MyTypeB }
}

-- Types used in the objects
MyTypeA ::= INTEGER (0..100)
MyTypeB ::= BOOLEAN

-- Usage of the parameterized type
TestExtension ::= SEQUENCE {
    extensionID    EXTENSION.&id ({ExtensionSet}),
    extensionValue EXTENSION.&Type({ExtensionSet}{@.extensionID})
}

END
