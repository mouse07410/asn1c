-- OK: -fallow-newer-modules accepts available module with newer OID arc
-- Imported OID version(3), available module version(5): newer -> accept

TestAllowNewer
	{ iso org(3) dod(6) internet(1) private(4) enterprise(1)
	  spelio(9363) software(1) asn1c(5) test(1) 204 }
	DEFINITIONS AUTOMATIC TAGS ::=
BEGIN

	IMPORTS ImportedType
	FROM ImportedModule204
	{ iso org(3) dod(6) internet(1) private(4) enterprise(1)
	  spelio(9363) software(1) asn1c(5) test(1) 204 version(3) }
	;

	Type ::= ImportedType

END


ImportedModule204
	{ iso org(3) dod(6) internet(1) private(4) enterprise(1)
	  spelio(9363) software(1) asn1c(5) test(1) 204 version(5) }
	DEFINITIONS AUTOMATIC TAGS ::=
BEGIN

	IMPORTS -- nothing --;

	ImportedType ::= INTEGER

END
