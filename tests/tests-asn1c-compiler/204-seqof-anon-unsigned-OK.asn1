-- OK: Regression: multiple SEQUENCE OF unsigned INTEGER in one module must compile
-- cleanly and emit per-element descriptors with field_unsigned=1.
-- Also tests constrained-range INTEGER (3..4) to verify UPER bit-width.
-- SET OF is tested separately in 205-setof-anon-unsigned-OK.asn1.
-- ENUMERATED is tested separately in 206-seqof-anon-enum-OK.asn1.

SeqOfUnsignedTest DEFINITIONS AUTOMATIC TAGS ::= BEGIN

SeqOfUInt32 ::= SEQUENCE OF INTEGER (0..4294967295)
SeqOf34     ::= SEQUENCE OF INTEGER (3..4)
SeqOfU64Max ::= SEQUENCE OF INTEGER (0..18446744073709551615)

END
