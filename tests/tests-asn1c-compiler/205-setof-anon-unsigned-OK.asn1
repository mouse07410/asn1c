-- OK: Regression: multiple SET OF unsigned INTEGER in one module must compile
-- cleanly.  Unsigned semantics (field_unsigned=1) must be present on each
-- per-element descriptor.
-- SEQUENCE OF is tested separately in 204-seqof-anon-unsigned-OK.asn1.
-- ENUMERATED is tested separately in 206-seqof-anon-enum-OK.asn1.

SetOfUnsignedTest DEFINITIONS AUTOMATIC TAGS ::= BEGIN

SetOfUInt32 ::= SET OF INTEGER (0..4294967295)
SetOf34     ::= SET OF INTEGER (3..4)
SetOfU64Max ::= SET OF INTEGER (0..18446744073709551615)

END
