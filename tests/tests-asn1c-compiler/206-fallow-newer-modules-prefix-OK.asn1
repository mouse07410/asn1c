-- OK: -fallow-newer-modules accepts available module whose base OID matches
-- and the available module adds exactly the 2 version arcs (release, minor)

TestAllowPrefix
	{ iso org(3) dod(6) internet(1) private(4) enterprise(1)
	  spelio(9363) software(1) asn1c(5) test(1) 206 }
	DEFINITIONS AUTOMATIC TAGS ::=
BEGIN

	IMPORTS ImportedType
	FROM ImportedModule206
	{ iso org(3) dod(6) internet(1) private(4)
	  enterprise(1) spelio(9363) software(1) asn1c(5) test(1) 206 }
	;

	Type ::= ImportedType

END


ImportedModule206
	{ iso org(3) dod(6) internet(1) private(4)
	  enterprise(1) spelio(9363) software(1) asn1c(5) test(1) 206 r17(17) v0(0) }
	DEFINITIONS AUTOMATIC TAGS ::=
BEGIN

	IMPORTS -- nothing --;

	ImportedType ::= INTEGER

END
