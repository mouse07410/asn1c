SetJerGroups DEFINITIONS AUTOMATIC TAGS ::= BEGIN

JerGroupSet ::= SET {
    root [0] INTEGER (0..255),
    ...,
    [[ first [1] INTEGER (0..255), flag [2] BOOLEAN OPTIONAL ]],
    [[ second [3] INTEGER (0..255) OPTIONAL, defaulted [4] INTEGER (0..255) DEFAULT 5 ]],
    extra [5] INTEGER (0..255) OPTIONAL
}

JerRecursive ::= SET {
    root [0] INTEGER,
    ...,
    [[ child [1] JerRecursive ]]
}

JerPlainSet ::= SET { root [0] INTEGER (0..255), flag [1] BOOLEAN OPTIONAL }

JerAllOptional ::= SET { flag [0] BOOLEAN OPTIONAL }

Id ::= INTEGER
P ::= CLASS { &id Id UNIQUE, &Type } WITH SYNTAX { ID &id TYPE &Type }
Payload ::= SEQUENCE { text OCTET STRING, number INTEGER }
Objs P ::= { { ID 1 TYPE Payload } | { ID 2 TYPE BOOLEAN } }
SetOpen ::= SET {
    id P.&id({Objs}),
    value P.&Type({Objs}{@id}) OPTIONAL
}
SeqOpen ::= SEQUENCE {
    id P.&id({Objs}),
    value P.&Type({Objs}{@id}) OPTIONAL
}

END
