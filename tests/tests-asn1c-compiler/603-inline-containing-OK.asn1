InlineContaining DEFINITIONS ::= BEGIN

OctetInteger ::= OCTET STRING (CONTAINING INTEGER (0..2))
BitInteger ::= BIT STRING (CONTAINING INTEGER (0..2))
OctetRecord ::= OCTET STRING (CONTAINING SEQUENCE { x BOOLEAN })
BitRecord ::= BIT STRING (CONTAINING SEQUENCE { x BOOLEAN })

END
