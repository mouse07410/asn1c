-- Test comprehensive &Type (typefieldreference) parsing
-- This test ensures that X.681 Information Object Class
-- type field references are properly recognized by the lexer

-- iso.org.dod.internet.private.enterprise (1.3.6.1.4.1)
-- .spelio.software.asn1c.test (9363.1.5.1)
-- .171

TestIOCTypeField
	{ iso org(3) dod(6) internet(1) private(4) enterprise(1)
		spelio(9363) software(1) asn1c(5) test(1) 171 }
	DEFINITIONS ::=
BEGIN

-- Test 1: Simple CLASS with single &Type field
SimpleClass ::= CLASS {
    &Type
}

-- Test 2: CLASS with multiple fields including &Type
MultiFieldClass ::= CLASS {
    &id INTEGER UNIQUE,
    &Type,
    &value &Type OPTIONAL
}

-- Test 3: CLASS with WITH SYNTAX containing &Type
WithSyntaxClass ::= CLASS {
    &id INTEGER UNIQUE,
    &Type
} WITH SYNTAX {
    &Type IDENTIFIED BY &id
}

-- Test 4: Various valid &Type field name patterns
VariousNamesClass ::= CLASS {
    &T,
    &Type,
    &MyType,
    &Type1,
    &Type-2,
    &My-Long-Type-Name-123,
    &TypeABC,
    &T1-T2-T3
}

-- Test 5: Using TYPE-IDENTIFIER standard class
TestTypeIdentifier ::= SEQUENCE {
    id TYPE-IDENTIFIER.&id,
    type TYPE-IDENTIFIER.&Type
}

-- Test 6: Nested field references
NestedClass ::= CLASS {
    &OuterType,
    &innerValue &OuterType
}

-- Test 7: CLASS field references via alias
MY-ID ::= TYPE-IDENTIFIER

TestAlias ::= SEQUENCE {
    field1 MY-ID.&id,
    field2 MY-ID.&Type
}

-- Test 8: Information object using &Type
testObject WithSyntaxClass ::= {
    INTEGER IDENTIFIED BY 42
}

END
