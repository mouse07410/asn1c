-- Unsupported alias composition; reject before creating Rust output.
-- Source: approved alias gate; 2026-11-01; responsible: asn1c maintainers.
AliasIntegerNegativeChain DEFINITIONS EXPLICIT TAGS ::= BEGIN
Base ::= INTEGER (0..5)
First ::= Base
Small ::= First
Packet ::= SEQUENCE { value Small }
END
