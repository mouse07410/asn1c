-- Unsupported alias composition; reject before creating Rust output.
-- Source: approved alias gate; 2026-11-01; responsible: asn1c maintainers.
AliasIntegerNegativeCycle DEFINITIONS EXPLICIT TAGS ::= BEGIN
Small ::= Loop
Loop ::= Small
END
