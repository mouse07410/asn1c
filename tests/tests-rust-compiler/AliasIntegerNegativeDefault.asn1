-- Unsupported alias composition; reject before creating Rust output.
-- Source: approved alias gate; 2026-11-01; responsible: asn1c maintainers.
AliasIntegerNegativeDefault DEFINITIONS EXPLICIT TAGS ::= BEGIN
Base ::= INTEGER (0..5)
Small ::= Base
Packet ::= SEQUENCE { value Small DEFAULT 2 }
END
