-- Unsupported alias composition; reject before creating Rust output.
-- Source: approved alias gate; 2026-11-01; responsible: asn1c maintainers.
AliasIntegerForeignBase DEFINITIONS ::= BEGIN
EXPORTS Base;
Base ::= INTEGER (0..5)
END
AliasIntegerForeignClient DEFINITIONS ::= BEGIN
IMPORTS Base FROM AliasIntegerForeignBase;
Small ::= Base
Packet ::= SEQUENCE { value Small }
END
