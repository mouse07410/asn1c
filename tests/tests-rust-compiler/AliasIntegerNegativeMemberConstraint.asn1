-- Unsupported alias composition; reject before creating Rust output.
-- Source: approved alias gate; 2026-11-01; responsible: asn1c maintainers.
AliasIntegerNegativeMemberConstraint DEFINITIONS EXPLICIT TAGS ::= BEGIN
Base ::= INTEGER (0..5)
Small ::= Base
Packet ::= SEQUENCE { value Small (1..4) }
END
