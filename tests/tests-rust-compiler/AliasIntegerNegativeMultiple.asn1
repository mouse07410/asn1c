-- Unsupported alias composition; reject before creating Rust output.
-- Source: approved alias gate; 2026-11-01; responsible: asn1c maintainers.
AliasIntegerNegativeMultiple DEFINITIONS EXPLICIT TAGS ::= BEGIN
Base ::= INTEGER (0..5)
Small ::= Base
Packet ::= SEQUENCE { first [0] IMPLICIT Small, second [1] IMPLICIT Small }
END
