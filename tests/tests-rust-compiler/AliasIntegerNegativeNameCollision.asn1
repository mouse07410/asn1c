-- Unsupported alias composition; reject before creating Rust output.
-- Source: approved alias gate; 2026-11-01; responsible: asn1c maintainers.
AliasIntegerNegativeNameCollision DEFINITIONS EXPLICIT TAGS ::= BEGIN
Base ::= INTEGER (0..5)
Foo-Bar ::= Base
FooBar ::= INTEGER (0..5)
END
