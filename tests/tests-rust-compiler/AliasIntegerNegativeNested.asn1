-- Unsupported alias composition; reject before creating Rust output.
-- Source: approved alias gate; 2026-11-01; responsible: asn1c maintainers.
AliasIntegerNegativeNested DEFINITIONS EXPLICIT TAGS ::= BEGIN
Base ::= INTEGER (0..5)
Small ::= Base
Packet ::= SEQUENCE { child SEQUENCE { value Small } }
END
