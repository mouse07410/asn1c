-- Unsupported alias composition; reject before creating Rust output.
-- Source: approved alias gate; 2026-11-01; responsible: asn1c maintainers.
AliasIntegerNegativeParameterizedBase DEFINITIONS EXPLICIT TAGS ::= BEGIN
Base { T } ::= INTEGER (0..5)
Small ::= Base { BOOLEAN }
END
