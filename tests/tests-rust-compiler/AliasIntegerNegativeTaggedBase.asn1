-- Unsupported alias composition; reject before creating Rust output.
-- Source: approved alias gate; 2026-11-01; responsible: asn1c maintainers.
AliasIntegerNegativeTaggedBase DEFINITIONS EXPLICIT TAGS ::= BEGIN
Base ::= [3] IMPLICIT INTEGER (0..5)
Small ::= Base
END
