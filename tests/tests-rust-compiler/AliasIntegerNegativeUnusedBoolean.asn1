-- Unsupported alias composition; reject before creating Rust output.
-- Source: approved alias gate; 2026-11-01; responsible: asn1c maintainers.
AliasIntegerNegativeUnusedBoolean DEFINITIONS EXPLICIT TAGS ::= BEGIN
Base ::= BOOLEAN
Small ::= Base
Packet ::= SEQUENCE { flag BOOLEAN }
END
