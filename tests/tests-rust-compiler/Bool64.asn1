Bool64 DEFINITIONS AUTOMATIC TAGS ::= BEGIN
Flags ::= SEQUENCE {
    bit0 BOOLEAN,
    bit1 BOOLEAN,
    bit2 BOOLEAN,
    bit3 BOOLEAN,
    bit4 BOOLEAN,
    bit5 BOOLEAN,
    bit6 BOOLEAN,
    bit7 BOOLEAN,
    bit8 BOOLEAN,
    bit9 BOOLEAN,
    bit10 BOOLEAN,
    bit11 BOOLEAN,
    bit12 BOOLEAN,
    bit13 BOOLEAN,
    bit14 BOOLEAN,
    bit15 BOOLEAN,
    bit16 BOOLEAN,
    bit17 BOOLEAN,
    bit18 BOOLEAN,
    bit19 BOOLEAN,
    bit20 BOOLEAN,
    bit21 BOOLEAN,
    bit22 BOOLEAN,
    bit23 BOOLEAN,
    bit24 BOOLEAN,
    bit25 BOOLEAN,
    bit26 BOOLEAN,
    bit27 BOOLEAN,
    bit28 BOOLEAN,
    bit29 BOOLEAN,
    bit30 BOOLEAN,
    bit31 BOOLEAN,
    bit32 BOOLEAN,
    bit33 BOOLEAN,
    bit34 BOOLEAN,
    bit35 BOOLEAN,
    bit36 BOOLEAN,
    bit37 BOOLEAN,
    bit38 BOOLEAN,
    bit39 BOOLEAN,
    bit40 BOOLEAN,
    bit41 BOOLEAN,
    bit42 BOOLEAN,
    bit43 BOOLEAN,
    bit44 BOOLEAN,
    bit45 BOOLEAN,
    bit46 BOOLEAN,
    bit47 BOOLEAN,
    bit48 BOOLEAN,
    bit49 BOOLEAN,
    bit50 BOOLEAN,
    bit51 BOOLEAN,
    bit52 BOOLEAN,
    bit53 BOOLEAN,
    bit54 BOOLEAN,
    bit55 BOOLEAN,
    bit56 BOOLEAN,
    bit57 BOOLEAN,
    bit58 BOOLEAN,
    bit59 BOOLEAN,
    bit60 BOOLEAN,
    bit61 BOOLEAN,
    bit62 BOOLEAN,
    bit63 BOOLEAN
}
END
