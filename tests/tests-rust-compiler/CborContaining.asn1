CborContaining DEFINITIONS ::= BEGIN
Inner ::= INTEGER (0..2)
Flag ::= BOOLEAN
Oct ::= OCTET STRING (CONTAINING Inner)
Bits ::= BIT STRING (CONTAINING Inner)
BoolOct ::= OCTET STRING (CONTAINING Flag)
BoolBits ::= BIT STRING (CONTAINING BOOLEAN)
END
