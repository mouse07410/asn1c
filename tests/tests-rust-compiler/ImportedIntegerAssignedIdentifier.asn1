ImportedIntegerAssignedBase { iso org(3) dod(6) internet(1) private(4) enterprise(1) 9201 }
    DEFINITIONS ::= BEGIN
Small ::= INTEGER (0..5)
END
ImportedIntegerAssignedClient DEFINITIONS ::= BEGIN
IMPORTS Small FROM ImportedIntegerAssignedBase
    { iso org(3) dod(6) internet(1) private(4) enterprise(1) 9201 };
Packet ::= SEQUENCE { value Small }
END
