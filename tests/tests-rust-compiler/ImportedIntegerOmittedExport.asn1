ImportedIntegerOmittedExportBase DEFINITIONS ::= BEGIN
EXPORTS Other;
Small ::= INTEGER (0..5)
Other ::= BOOLEAN
END
ImportedIntegerOmittedExportClient DEFINITIONS ::= BEGIN
IMPORTS Small FROM ImportedIntegerOmittedExportBase;
Packet ::= SEQUENCE { value Small }
END
