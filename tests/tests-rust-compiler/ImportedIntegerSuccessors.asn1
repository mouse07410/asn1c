ImportedIntegerSuccessorClient
    { iso org(3) dod(6) internet(1) private(4) enterprise(1) 9202 }
    DEFINITIONS ::= BEGIN
IMPORTS Small FROM ImportedIntegerSuccessorBase
    { iso org(3) dod(6) internet(1) private(4) enterprise(1) 9202 minor-version-1(1) }
    WITH SUCCESSORS;
Packet ::= SEQUENCE { value Small }
END
ImportedIntegerSuccessorBase
    { iso org(3) dod(6) internet(1) private(4) enterprise(1) 9202 minor-version-5(5) }
    DEFINITIONS ::= BEGIN
Small ::= INTEGER (0..5)
END
