ImportedIntegerUnusedUnsupportedBase DEFINITIONS ::= BEGIN
Flag ::= BOOLEAN
END
ImportedIntegerUnusedUnsupportedClient DEFINITIONS ::= BEGIN
IMPORTS Flag FROM ImportedIntegerUnusedUnsupportedBase;
Packet ::= BOOLEAN
END
