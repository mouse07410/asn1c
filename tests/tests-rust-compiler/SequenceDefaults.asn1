SequenceDefaults DEFINITIONS AUTOMATIC TAGS ::= BEGIN

DefaultPacket ::= SEQUENCE {
    before BOOLEAN OPTIONAL,
    enabled BOOLEAN DEFAULT FALSE,
    count INTEGER (0..3) DEFAULT 1,
    active BOOLEAN DEFAULT TRUE,
    after BOOLEAN OPTIONAL,
    tail INTEGER (0..3)
}

WideDefault ::= SEQUENCE {
    value INTEGER (-9223372036854775808..9223372036854775807)
        DEFAULT -9223372036854775808
}

END
