TaggedSetC DEFINITIONS AUTOMATIC TAGS ::= BEGIN

TaggedSetParity ::= SET {
    high [128] IMPLICIT BOOLEAN OPTIONAL,
    marker [31] IMPLICIT NULL,
    count [2] IMPLICIT INTEGER (-3..3) DEFAULT 1,
    flag BOOLEAN DEFAULT FALSE,
    second [127] IMPLICIT BOOLEAN OPTIONAL
}

END
