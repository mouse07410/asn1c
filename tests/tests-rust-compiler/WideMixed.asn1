WideMixed DEFINITIONS AUTOMATIC TAGS ::= BEGIN
Flags ::= SEQUENCE {
    bit0 BOOLEAN DEFAULT TRUE,
    bit1 BOOLEAN,
    bit2 BOOLEAN OPTIONAL,
    bit3 BOOLEAN,
    bit4 BOOLEAN DEFAULT TRUE,
    bit5 BOOLEAN,
    bit6 BOOLEAN DEFAULT TRUE,
    bit7 BOOLEAN,
    bit8 BOOLEAN DEFAULT TRUE,
    bit9 BOOLEAN,
    bit10 BOOLEAN DEFAULT TRUE,
    bit11 BOOLEAN,
    bit12 BOOLEAN DEFAULT TRUE,
    bit13 BOOLEAN,
    bit14 BOOLEAN DEFAULT TRUE,
    bit15 BOOLEAN,
    bit16 BOOLEAN DEFAULT TRUE,
    bit17 BOOLEAN,
    bit18 BOOLEAN OPTIONAL,
    bit19 BOOLEAN,
    bit20 BOOLEAN DEFAULT TRUE,
    bit21 BOOLEAN,
    bit22 BOOLEAN DEFAULT TRUE,
    bit23 BOOLEAN,
    bit24 BOOLEAN DEFAULT TRUE,
    bit25 BOOLEAN,
    bit26 BOOLEAN DEFAULT TRUE,
    bit27 BOOLEAN,
    bit28 BOOLEAN DEFAULT TRUE,
    bit29 BOOLEAN,
    bit30 BOOLEAN DEFAULT TRUE,
    bit31 BOOLEAN,
    bit32 BOOLEAN DEFAULT TRUE,
    bit33 BOOLEAN,
    bit34 BOOLEAN OPTIONAL,
    bit35 BOOLEAN,
    bit36 BOOLEAN DEFAULT TRUE,
    bit37 BOOLEAN,
    bit38 BOOLEAN DEFAULT TRUE,
    bit39 BOOLEAN,
    bit40 BOOLEAN DEFAULT TRUE,
    bit41 BOOLEAN,
    bit42 BOOLEAN DEFAULT TRUE,
    bit43 BOOLEAN,
    bit44 BOOLEAN DEFAULT TRUE,
    bit45 BOOLEAN,
    bit46 BOOLEAN DEFAULT TRUE,
    bit47 BOOLEAN,
    bit48 BOOLEAN DEFAULT TRUE,
    bit49 BOOLEAN,
    bit50 BOOLEAN OPTIONAL,
    bit51 BOOLEAN,
    bit52 BOOLEAN DEFAULT TRUE,
    bit53 BOOLEAN,
    bit54 BOOLEAN DEFAULT TRUE,
    bit55 BOOLEAN,
    bit56 BOOLEAN DEFAULT TRUE,
    bit57 BOOLEAN,
    bit58 BOOLEAN DEFAULT TRUE,
    bit59 BOOLEAN,
    bit60 BOOLEAN DEFAULT TRUE,
    bit61 BOOLEAN,
    bit62 BOOLEAN DEFAULT TRUE,
    bit63 BOOLEAN
}
END
