WideOptional DEFINITIONS AUTOMATIC TAGS ::= BEGIN
Flags ::= SEQUENCE {
    bit0 BOOLEAN,
    bit1 BOOLEAN,
    bit2 BOOLEAN,
    bit3 BOOLEAN,
    bit4 BOOLEAN OPTIONAL,
    bit5 BOOLEAN OPTIONAL,
    bit6 BOOLEAN OPTIONAL,
    bit7 BOOLEAN OPTIONAL,
    bit8 BOOLEAN OPTIONAL,
    bit9 BOOLEAN OPTIONAL,
    bit10 BOOLEAN OPTIONAL,
    bit11 BOOLEAN OPTIONAL,
    bit12 BOOLEAN OPTIONAL,
    bit13 BOOLEAN OPTIONAL,
    bit14 BOOLEAN OPTIONAL,
    bit15 BOOLEAN OPTIONAL,
    bit16 BOOLEAN OPTIONAL,
    bit17 BOOLEAN OPTIONAL,
    bit18 BOOLEAN OPTIONAL,
    bit19 BOOLEAN OPTIONAL,
    bit20 BOOLEAN OPTIONAL,
    bit21 BOOLEAN OPTIONAL,
    bit22 BOOLEAN OPTIONAL,
    bit23 BOOLEAN OPTIONAL,
    bit24 BOOLEAN OPTIONAL,
    bit25 BOOLEAN OPTIONAL,
    bit26 BOOLEAN OPTIONAL,
    bit27 BOOLEAN OPTIONAL,
    bit28 BOOLEAN OPTIONAL,
    bit29 BOOLEAN OPTIONAL,
    bit30 BOOLEAN OPTIONAL,
    bit31 BOOLEAN OPTIONAL,
    bit32 BOOLEAN OPTIONAL,
    bit33 BOOLEAN OPTIONAL,
    bit34 BOOLEAN OPTIONAL,
    bit35 BOOLEAN OPTIONAL,
    bit36 BOOLEAN OPTIONAL,
    bit37 BOOLEAN OPTIONAL,
    bit38 BOOLEAN OPTIONAL,
    bit39 BOOLEAN OPTIONAL,
    bit40 BOOLEAN OPTIONAL,
    bit41 BOOLEAN OPTIONAL,
    bit42 BOOLEAN OPTIONAL,
    bit43 BOOLEAN OPTIONAL,
    bit44 BOOLEAN OPTIONAL,
    bit45 BOOLEAN OPTIONAL,
    bit46 BOOLEAN OPTIONAL,
    bit47 BOOLEAN OPTIONAL,
    bit48 BOOLEAN OPTIONAL,
    bit49 BOOLEAN OPTIONAL,
    bit50 BOOLEAN OPTIONAL,
    bit51 BOOLEAN OPTIONAL,
    bit52 BOOLEAN OPTIONAL,
    bit53 BOOLEAN OPTIONAL,
    bit54 BOOLEAN OPTIONAL,
    bit55 BOOLEAN OPTIONAL,
    bit56 BOOLEAN OPTIONAL,
    bit57 BOOLEAN OPTIONAL,
    bit58 BOOLEAN OPTIONAL,
    bit59 BOOLEAN OPTIONAL,
    bit60 BOOLEAN OPTIONAL,
    bit61 BOOLEAN OPTIONAL,
    bit62 BOOLEAN OPTIONAL,
    bit63 BOOLEAN OPTIONAL
}
END
